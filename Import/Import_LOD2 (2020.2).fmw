FME workspace Import_LOD2 (2020.2).fmw

Parameters:
- SourceDataset_CITYGML_3 = C:\Users\tomben1\OneDrive - Malmö stad\Documents\Master_thesis\Script\CityGML_LOD2\output_script\undervisningshuset_lod_2.gml   # Source CityGML File(s)
- SourceDataset_CITYGML = C:\Users\tomben1\OneDrive - Malmö stad\Documents\Master_thesis\Script\CityGML_LOD2\output_script\kanaan_lod2.gml   # Source CityGML File(s)

Readers:
- CITYGML_1: CITYGML from $(SourceDataset_CITYGML_3)
- CITYGML_2: CITYGML from $(SourceDataset_CITYGML)

Note: Building: undervisningshuset_lod_2 [CITYGML]
Building (reader CITYGML_1)
    attributes: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
Note: Building: kanaan_lod2 [CITYGML]
Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
    -> GeometryPartExtractor
    -> GeometryExtractor
GeometryExtractor
    ATTR = _geometry_bbox
    KIND_LONG = OGC Well Known Text
    OGCVERSION = 1.2
    OGC_WKT_PRECISION_DISPLAY = 64-bit
    PREFER_POLYGON_OVER_SURFACE = No
    REMOVE_GEOMETRY = Yes
    -> SQLExecutor [INITIATOR]
SQLExecutor
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.cityobject("objectclass_id", "gmlid", "envelope", "updating_person")
      SELECT '26', '@Value(gml_id)', citydb.box2envelope(st_3dextent('@Value(_geometry_bbox)')),'Tom_Bendiksen'
      FROM citydb.cityobject
    INITIATOR -> SQLExecutor_2 [INITIATOR]
SQLExecutor_2
    COMBINE_ATTRS = Result Attributes Only
    COMBINE_GEOM = Initiator Geometry Only
    DATASET = postgres
    EXPOSED_ATTRIBUTE_LIST = maxid,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as maxid, '@Value(gml_id)' as gmlid
      FROM citydb.cityobject
      order by maxid desc
      limit 1
    RESULT -> FeatureMerger [SUPPLIER]
    RESULT -> FeatureMerger_2 [SUPPLIER]
Note: Slår sammen geometrier for lagring i solid_geometry som finnes i surface_geometry
Aggregator
    ACCUM_ATTRS_NAME = Use Attributes From One Feature
    AGGREGATE_TYPE = Homogeneous Collection (If Possible)
    GROUP_BY = gml_id
    MODE = Geometry - Assemble One Level
    SEP = ,
    AGGREGATE -> GeometryExtractor_3
Note: Endrer geometrier til OGC WKT
GeometryExtractor_3
    ATTR = _geometry_solid
    KIND_LONG = OGC Well Known Text
    OGCVERSION = 1.2
    OGC_WKT_PRECISION_DISPLAY = 64-bit
    PREFER_POLYGON_OVER_SURFACE = No
    REMOVE_GEOMETRY = No
    -> StringReplacer
Note: Erstatter multipolygon med polyhedralsurface for å bruke i st_makesolid
StringReplacer
    CASE = NO
    FIND_TEXT = MULTIPOLYGON
    NO_MATCH = _FME_NO_OP_
    REGEXP = NO
    REPLACE_TEXT = POLYHEDRALSURFACE
    SRC_ATTRS = _geometry_solid
    -> FeatureMerger [REQUESTOR]
FeatureMerger
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> UUIDGenerator
    MERGED -> UUIDGenerator_2
UUIDGenerator
    UUID_ATTR = _uuid
    -> AttributeCreator
AttributeCreator
    ATTR_TABLE:
      SET_TO UUID = UUID_@Value(_uuid)
      SET_TO SQL = INSERT INTO citydb.surface_geometry("id", "gmlid", "parent_id", "root_id", "is_solid", "is_composite", "is_triangulated", "is_xlink", "is_reverse", "solid_geometry", "cityobject_id")
        SELECT nextval('surface_geometry_seq'), '@Value(UUID)', NULL, currval('surface_geometry_seq'), '1', '0', '0', '0', '0', st_setsrid(st_makesolid('@Value(_geometry_solid)'), 3008), '@Value(maxid)'
      SET_TO TYPE = 1
    -> Sorter
    -> FeatureMerger_3 [SUPPLIER]
UUIDGenerator_2
    UUID_ATTR = _uuid
    -> AttributeCreator_2
AttributeCreator_2
    ATTR_TABLE:
      SET_TO UUID = UUID_@Value(_uuid)
      SET_TO SQL = INSERT INTO citydb.surface_geometry("id", "gmlid", "parent_id", "root_id", "is_solid", "is_composite", "is_triangulated", "is_xlink", "is_reverse", "cityobject_id")
        SELECT nextval('surface_geometry_seq'), '@Value(UUID)', currval('surface_geometry_seq')-1, currval('surface_geometry_seq')-1, '0', '1', '0', '0', '0', '@Value(maxid)'
      SET_TO TYPE = 2
    -> Sorter
GeometryExtractor_2
    ATTR = _geometry_polygon
    KIND_LONG = OGC Well Known Text
    OGCVERSION = 1.2
    OGC_WKT_PRECISION_DISPLAY = 64-bit
    PREFER_POLYGON_OVER_SURFACE = No
    REMOVE_GEOMETRY = No
    -> FeatureMerger_2 [REQUESTOR]
FeatureMerger_2
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> UUIDGenerator_3
UUIDGenerator_3
    UUID_ATTR = _uuid
    -> Counter
Counter
    CNT_ATTR = _count
    DOMAIN = @Value(maxid)
    SCOPE = Global
    START = 2
    -> AttributeCreator_3
AttributeCreator_3
    ATTR_TABLE:
      SET_TO UUID = UUID_@Value(_uuid)
      SET_TO SQL = insert into citydb.surface_geometry ("id", "gmlid", "parent_id", "root_id", "is_solid", "is_composite", "is_triangulated", "is_xlink", "is_reverse", "geometry", "cityobject_id")
        select nextval('surface_geometry_seq'), '@Value(gml_id_polygon)', currval('surface_geometry_seq')-(@Value(_count)-1),  currval('surface_geometry_seq')-@Value(_count), '0', '0', '0', '1', '0', st_setsrid('@Value(_geometry_polygon)'::geometry, 3008), @Value(maxid)
      SET_TO TYPE = 3
    -> Sorter
Sorter
    SORT_PARM = maxid NUMERIC ASCENDING TYPE NUMERIC ASCENDING _count NUMERIC ASCENDING
    SORTED -> SQLExecutor_3 [INITIATOR]
FeatureHolder
    -> Sampler
Sampler
    RATE = 1
    SAMPLE_MODE = No
    SAMPLE_TYPE_LONG = First N Features
    SAMPLED -> SQLExecutor_4 [INITIATOR]
SQLExecutor_4
    COMBINE_ATTRS = Result Attributes Only
    COMBINE_GEOM = Initiator Geometry Only
    DATASET = postgres
    EXPOSED_ATTRIBUTE_LIST = id,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = select id, gmlid from surface_geometry
    RESULT -> FeatureMerger_3 [REQUESTOR]
FeatureMerger_3
    ATTR_ACCUM_MODE = Merge Supplier
    ATTR_CONFLICT_RES = Use Requestor
    IGNORE_NULLS = No
    JOIN_KEYS = @Value(gmlid) @Value(UUID) AUTO
    MERGE_TYPE = Attributes Only
    PROCESS_DUPS = NO
    REJECT_NULL_MISSING_KEYS = No
    SUPPLIERS_FIRST = No
    MERGED -> SQLExecutor_5 [INITIATOR]
AttributeKeeper_2_id
    CREATE_BULK_MODE_FEATURES = NO
    KEEP_ATTRS = maxid
    -> AttributeCreator_7
AttributeCreator_7
    ATTR_TABLE = SET_TO mergeid = 1
    -> GeometryRemover
    -> FeatureMerger_4 [SUPPLIER]
    -> FeatureMerger_9 [SUPPLIER]
    -> FeatureMerger_12 [SUPPLIER]
GeometryRemover
    -> FeatureHolder_7
FeatureHolder_7
    -> Sampler_7
Sampler_7
    RATE = 1
    SAMPLE_MODE = No
    SAMPLE_TYPE_LONG = First N Features
    SAMPLED -> FeatureReader_3 [INITIATOR]
Aggregator_9
    ACCUM_ATTRS_NAME = Use Attributes From One Feature
    AGGREGATE_TYPE = Homogeneous Collection (If Possible)
    GROUP_BY = gml_id
    MODE = Geometry - Assemble One Level
    SEP = ,
    AGGREGATE -> UUIDGenerator_6
FeatureHolder_4
    -> Sampler_2
FeatureHolder_6
    -> Sampler_6
Sampler_6
    RATE = 1
    SAMPLE_MODE = No
    SAMPLE_TYPE_LONG = First N Features
    SAMPLED -> FeatureReader [INITIATOR]
Aggregator_5
    ACCUM_ATTRS_NAME = Use Attributes From One Feature
    AGGREGATE_TYPE = Homogeneous Collection (If Possible)
    GROUP_BY = gml_id
    MODE = Geometry - Assemble One Level
    SEP = ,
    AGGREGATE -> UUIDGenerator_7
FeatureHolder_5
    -> Sampler_5
Sampler_5
    RATE = 1
    SAMPLE_MODE = No
    SAMPLE_TYPE_LONG = First N Features
    SAMPLED -> FeatureReader_2 [INITIATOR]
Aggregator_6
    ACCUM_ATTRS_NAME = Use Attributes From One Feature
    AGGREGATE_TYPE = Homogeneous Collection (If Possible)
    GROUP_BY = gml_id
    MODE = Geometry - Assemble One Level
    SEP = ,
    AGGREGATE -> UUIDGenerator_9

Bookmark: Bryter opp soliden til polygoner for lagring i surface_geometry
GeometryPartExtractor
    GQUERY:
      for $geom in //geometry
      where $geom/@fme_geometry_type = 'IFMEFace'
      return number($geom/@fme_id)
    EXTRACTED -> GeometryPropertyExtractor_2
GeometryPropertyExtractor_2
    EXTRACTTYPE_PARAM = Traits
    GQUERY:
      for $geom in //geometry
      where $geom/@fme_geometry_type = 'IFMEFace'
      return number($geom/@fme_id)
    PREFIX_EXTRACTED_TRAITS = Yes
    TRAIT_ATTR_LIST = gml_id,No
    EXTRACTED -> AttributeExposer_2
AttributeExposer_2
    ATTR_LIST = surfaceMember.gml_id
    -> AttributeRenamer_2
AttributeRenamer_2
    ATTR_TABLE = RENAME_SET_DEFAULT surfaceMember.gml_id > gml_id_polygon
    -> GeometryCoercer
GeometryCoercer
    GQUERY:
      for $geom in //geometry
      where $geom/count(parent::geometry) = 0
      return number($geom/@fme_id)
    KIND = fme_polygon
    COERCED -> AttributeKeeper
AttributeKeeper
    CREATE_BULK_MODE_FEATURES = NO
    KEEP_ATTRS = gml_id,gml_id_polygon
    -> GeometryExtractor_2
    -> Aggregator

Bookmark: surface_geometry
SQLExecutor_3
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = @Value(SQL)
    INITIATOR -> FeatureHolder

Bookmark: Writing to building
SQLExecutor_5
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.building("id", "objectclass_id", "building_root_id", "lod2_solid_id")
      SELECT @Value(maxid), '26', @Value(maxid), @Value(id)
    INITIATOR -> AttributeKeeper_2_id

Bookmark: Writing GroundSurface to cityobject and storing cityobjectid and gmlid for processing
FeatureReader_3
    ATTRIBUTES = Building,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_class,citygml_class_codeSpace,citygml_function{},citygml_function{}.codeSpace,citygml_usage{},citygml_usage{}.codeSpace,citygml_year_of_construction,citygml_year_of_demolition,citygml_roof_type,citygml_roof_type_codeSpace,citygml_measured_height,citygml_measured_height_units,citygml_storeys_above_ground,citygml_storeys_below_ground,citygml_storey_heights_above_ground,citygml_storey_heights_above_ground_units,citygml_storey_heights_below_ground,citygml_storey_heights_below_ground_units,citygml_outer_building_installation{}.xlink_href,citygml_interior_building_installation{}.xlink_href,citygml_bounded_by{}.xlink_href,citygml_level_of_detail{},citygml_interior_room{}.xlink_href,citygml_consists_of_building_part{}.xlink_href,citygml_address{}.xlink_href,fme_geometry{0},fme_geometry{1},fme_geometry{2},fme_geometry{3},fme_geometry{4},fme_geometry{5},fme_geometry{6},fme_geometry{7}",CityModel,"gml_id,citygml_target_uri,gml_description,gml_name,citygml_city_object_member{}.xlink_href,citygml_appearance_member{}.xlink_href,gml_feature_member{}.xlink_href,fme_geometry{0}",GroundSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}",RoofSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}",WallSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}"
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = C:\Users\tomben1\OneDrive - Malmö stad\Documents\Master_thesis\Script\CityGML_LOD2\output_script\kanaan_lod2.gml
    FEATURETYPES = GroundSurface
    FORMAT = CITYGML
    INTERACT = <No Spatial Filter>
    OUTPUT_FEATURES_DISPLAY = Schema and Data Features
    GroundSurface -> Aggregator_10
    GroundSurface -> GeometryPartExtractor_3
Aggregator_10
    ACCUM_ATTRS_NAME = Use Attributes From One Feature
    AGGREGATE_TYPE = Homogeneous Collection (If Possible)
    GROUP_BY = gml_id
    MODE = Geometry - Assemble One Level
    SEP = ,
    AGGREGATE -> GeometryExtractor_5
GeometryExtractor_5
    ATTR = _geometry_bbox
    KIND_LONG = OGC Well Known Text
    OGCVERSION = 1.2
    OGC_WKT_PRECISION_DISPLAY = 64-bit
    PREFER_POLYGON_OVER_SURFACE = No
    REMOVE_GEOMETRY = Yes
    -> SQLExecutor_9 [INITIATOR]
SQLExecutor_9
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.cityobject("objectclass_id", "gmlid", "envelope", "updating_person")
      SELECT '35', '@Value(gml_id)', citydb.box2envelope(st_3dextent('@Value(_geometry_bbox)')),'Tom_Bendiksen'
    INITIATOR -> SQLExecutor_11 [INITIATOR]
SQLExecutor_11
    COMBINE_ATTRS = Result Attributes Only
    COMBINE_GEOM = Initiator Geometry Only
    DATASET = postgres
    EXPOSED_ATTRIBUTE_LIST = cityobjectid,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as cityobjectid, '@Value(gml_id)' as gmlid
      FROM citydb.cityobject
      WHERE cityobject.gmlid = '@Value(gml_id)'
    RESULT -> FeatureMerger_8 [SUPPLIER]
GeometryPartExtractor_3
    GQUERY:
      for $geom in //geometry
      where $geom/@fme_geometry_type = 'IFMEFace'
      return number($geom/@fme_id)
    EXTRACTED -> GeometryPropertyExtractor_3
GeometryPropertyExtractor_3
    EXTRACTTYPE_PARAM = Traits
    GQUERY:
      for $geom in //geometry
      where $geom/@fme_geometry_type = 'IFMEFace'
      return number($geom/@fme_id)
    PREFIX_EXTRACTED_TRAITS = Yes
    TRAIT_ATTR_LIST = gml_id,No
    EXTRACTED -> AttributeExposer_3
AttributeExposer_3
    ATTR_LIST = surfaceMember.gml_id
    -> AttributeRenamer_3
AttributeRenamer_3
    ATTR_TABLE = RENAME_SET_DEFAULT surfaceMember.gml_id > gml_id_polygon
    -> GeometryCoercer_3
GeometryCoercer_3
    GQUERY:
      for $geom in //geometry
      where $geom/count(parent::geometry) = 0
      return number($geom/@fme_id)
    KIND = fme_polygon
    COERCED -> GeometryExtractor_6
GeometryExtractor_6
    ATTR = _geometry_polygon
    KIND_LONG = OGC Well Known Text
    OGCVERSION = 1.2
    OGC_WKT_PRECISION_DISPLAY = 64-bit
    PREFER_POLYGON_OVER_SURFACE = No
    REMOVE_GEOMETRY = No
    -> FeatureMerger_8 [REQUESTOR]
FeatureMerger_8
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> Aggregator_4
    MERGED -> Aggregator_9

Bookmark: Writing GroundSurface to surface_geometry
Aggregator_4
    ACCUM_ATTRS_NAME = Use Attributes From One Feature
    AGGREGATE_TYPE = Homogeneous Collection (If Possible)
    GROUP_BY = gml_id
    MODE = Geometry - Assemble One Level
    SEP = ,
    AGGREGATE -> UUIDGenerator_5
UUIDGenerator_5
    UUID_ATTR = _uuid
    -> AttributeCreator_15
AttributeCreator_15
    ATTR_TABLE:
      SET_TO UUID = UUID_@Value(_uuid)
      SET_TO SQL = INSERT INTO citydb.surface_geometry("id", "gmlid", "parent_id", "root_id", "is_solid", "is_composite", "is_triangulated", "is_xlink", "is_reverse", "cityobject_id")
        SELECT nextval('surface_geometry_seq'), '@Value(gml_id)', NULL, currval('surface_geometry_seq'), '0', '0', '0', '0', '0', '@Value(cityobjectid)'
      SET_TO TYPE = 1
    -> Sorter_5
    -> FeatureMerger_7 [SUPPLIER]
UUIDGenerator_6
    UUID_ATTR = _uuid
    -> Counter_3
Counter_3
    CNT_ATTR = _count
    DOMAIN = @Value(cityobjectid)
    SCOPE = Global
    START = 1
    -> AttributeCreator_16
AttributeCreator_16
    ATTR_TABLE:
      SET_TO UUID = UUID_@Value(_uuid)
      SET_TO SQL = INSERT INTO citydb.surface_geometry("id", "gmlid", "parent_id", "root_id", "is_solid", "is_composite", "is_triangulated", "is_xlink", "is_reverse", "geometry", "cityobject_id")
        SELECT nextval('surface_geometry_seq'), '@Value(gml_id_polygon)',  currval('surface_geometry_seq')-1,  currval('surface_geometry_seq')-1, '0', '0', '0', '1', '0', st_setsrid('@Value(_geometry_polygon)'::geometry, 3008), '@Value(cityobjectid)'



      SET_TO TYPE = 2
    -> Sorter_5
Sorter_5
    SORT_PARM = cityobjectid NUMERIC ASCENDING TYPE NUMERIC ASCENDING
    SORTED -> SQLExecutor_8 [INITIATOR]
SQLExecutor_8
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = @Value(SQL)
    INITIATOR -> FeatureHolder_4

Bookmark: Writing GroundSurface to thematic_surface
Sampler_2
    RATE = 1
    SAMPLE_MODE = No
    SAMPLE_TYPE_LONG = First N Features
    SAMPLED -> SQLExecutor_12 [INITIATOR]
SQLExecutor_12
    COMBINE_ATTRS = Result Attributes Only
    COMBINE_GEOM = Initiator Geometry Only
    DATASET = postgres
    EXPOSED_ATTRIBUTE_LIST = lod2multisurfaceid,gmlid,cityobject_id
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      select root_id as lod2multisurfaceid, gmlid, cityobject_id as cityobjectid
      from surface_geometry
    RESULT -> FeatureMerger_7 [REQUESTOR]
FeatureMerger_7
    ATTR_ACCUM_MODE = Merge Supplier
    ATTR_CONFLICT_RES = Use Requestor
    IGNORE_NULLS = No
    JOIN_KEYS = @Value(gmlid) @Value(gml_id) AUTO
    MERGE_TYPE = Attributes Only
    PROCESS_DUPS = NO
    REJECT_NULL_MISSING_KEYS = No
    SUPPLIERS_FIRST = No
    MERGED -> AttributeCreator_4
AttributeCreator_4
    ATTR_TABLE = SET_TO mergeid = 1
    -> FeatureMerger_4 [REQUESTOR]
FeatureMerger_4
    ATTR_ACCUM_MODE = Merge Supplier
    ATTR_CONFLICT_RES = Use Requestor
    IGNORE_NULLS = No
    JOIN_KEYS = @Value(mergeid) @Value(mergeid) AUTO
    MERGE_TYPE = Attributes Only
    PROCESS_DUPS = NO
    REJECT_NULL_MISSING_KEYS = No
    SUPPLIERS_FIRST = No
    MERGED -> SQLExecutor_7 [INITIATOR]
SQLExecutor_7
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.thematic_surface("id", "objectclass_id", "building_id", "lod2_multi_surface_id")
      SELECT '@Value(cityobjectid)', '35', '@Value(maxid)', '@Value(lod2multisurfaceid)'
    INITIATOR -> FeatureHolder_6

Bookmark: Writing WallSurface to cityobject and storing cityobjectid and gmlid for processing
FeatureReader
    ATTRIBUTES = Building,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_class,citygml_class_codeSpace,citygml_function{},citygml_function{}.codeSpace,citygml_usage{},citygml_usage{}.codeSpace,citygml_year_of_construction,citygml_year_of_demolition,citygml_roof_type,citygml_roof_type_codeSpace,citygml_measured_height,citygml_measured_height_units,citygml_storeys_above_ground,citygml_storeys_below_ground,citygml_storey_heights_above_ground,citygml_storey_heights_above_ground_units,citygml_storey_heights_below_ground,citygml_storey_heights_below_ground_units,citygml_outer_building_installation{}.xlink_href,citygml_interior_building_installation{}.xlink_href,citygml_bounded_by{}.xlink_href,citygml_level_of_detail{},citygml_interior_room{}.xlink_href,citygml_consists_of_building_part{}.xlink_href,citygml_address{}.xlink_href,fme_geometry{0},fme_geometry{1},fme_geometry{2},fme_geometry{3},fme_geometry{4},fme_geometry{5},fme_geometry{6},fme_geometry{7}",CityModel,"gml_id,citygml_target_uri,gml_description,gml_name,citygml_city_object_member{}.xlink_href,citygml_appearance_member{}.xlink_href,gml_feature_member{}.xlink_href,fme_geometry{0}",GroundSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}",RoofSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}",WallSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}"
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = C:\Users\tomben1\OneDrive - Malmö stad\Documents\Master_thesis\Script\CityGML_LOD2\output_script\kanaan_lod2.gml
    FEATURETYPES = WallSurface
    FORMAT = CITYGML
    INTERACT = <No Spatial Filter>
    OUTPUT_FEATURES_DISPLAY = Schema and Data Features
    WallSurface -> Aggregator_8
    WallSurface -> GeometryPartExtractor_2
Aggregator_8
    ACCUM_ATTRS_NAME = Use Attributes From One Feature
    AGGREGATE_TYPE = Homogeneous Collection (If Possible)
    GROUP_BY = gml_id
    MODE = Geometry - Assemble One Level
    SEP = ,
    AGGREGATE -> GeometryExtractor_4
GeometryExtractor_4
    ATTR = _geometry_bbox
    KIND_LONG = OGC Well Known Text
    OGCVERSION = 1.2
    OGC_WKT_PRECISION_DISPLAY = 64-bit
    PREFER_POLYGON_OVER_SURFACE = No
    REMOVE_GEOMETRY = Yes
    -> SQLExecutor_6 [INITIATOR]
SQLExecutor_6
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.cityobject("objectclass_id", "gmlid", "envelope", "updating_person")
      SELECT '34', '@Value(gml_id)', citydb.box2envelope(st_3dextent('@Value(_geometry_bbox)')),'Tom_Bendiksen'
    INITIATOR -> SQLExecutor_10 [INITIATOR]
SQLExecutor_10
    COMBINE_ATTRS = Result Attributes Only
    COMBINE_GEOM = Initiator Geometry Only
    DATASET = postgres
    EXPOSED_ATTRIBUTE_LIST = cityobjectid,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as cityobjectid, '@Value(gml_id)' as gmlid
      FROM citydb.cityobject
      WHERE cityobject.gmlid = '@Value(gml_id)'
    RESULT -> FeatureMerger_5 [SUPPLIER]
GeometryPartExtractor_2
    GQUERY:
      for $geom in //geometry
      where $geom/@fme_geometry_type = 'IFMEFace'
      return number($geom/@fme_id)
    EXTRACTED -> GeometryPropertyExtractor
GeometryPropertyExtractor
    EXTRACTTYPE_PARAM = Traits
    GQUERY:
      for $geom in //geometry
      where $geom/@fme_geometry_type = 'IFMEFace'
      return number($geom/@fme_id)
    PREFIX_EXTRACTED_TRAITS = Yes
    TRAIT_ATTR_LIST = gml_id,No
    EXTRACTED -> AttributeExposer
AttributeExposer
    ATTR_LIST = surfaceMember.gml_id
    -> AttributeRenamer
AttributeRenamer
    ATTR_TABLE = RENAME_SET_DEFAULT surfaceMember.gml_id > gml_id_polygon
    -> GeometryCoercer_2
GeometryCoercer_2
    GQUERY:
      for $geom in //geometry
      where $geom/count(parent::geometry) = 0
      return number($geom/@fme_id)
    KIND = fme_polygon
    COERCED -> GeometryExtractor_7
GeometryExtractor_7
    ATTR = _geometry_polygon
    KIND_LONG = OGC Well Known Text
    OGCVERSION = 1.2
    OGC_WKT_PRECISION_DISPLAY = 64-bit
    PREFER_POLYGON_OVER_SURFACE = No
    REMOVE_GEOMETRY = No
    -> FeatureMerger_5 [REQUESTOR]
FeatureMerger_5
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> Aggregator_2
    MERGED -> Aggregator_5

Bookmark: Writing WallSurface to surface_geometry
Aggregator_2
    ACCUM_ATTRS_NAME = Use Attributes From One Feature
    AGGREGATE_TYPE = Homogeneous Collection (If Possible)
    GROUP_BY = gml_id
    MODE = Geometry - Assemble One Level
    SEP = ,
    AGGREGATE -> UUIDGenerator_4
UUIDGenerator_4
    UUID_ATTR = _uuid
    -> AttributeCreator_5
AttributeCreator_5
    ATTR_TABLE:
      SET_TO UUID = UUID_@Value(_uuid)
      SET_TO SQL = INSERT INTO citydb.surface_geometry("id", "gmlid", "parent_id", "root_id", "is_solid", "is_composite", "is_triangulated", "is_xlink", "is_reverse", "cityobject_id")
        SELECT nextval('surface_geometry_seq'), '@Value(gml_id)', NULL, currval('surface_geometry_seq'), '0', '0', '0', '0', '0', '@Value(cityobjectid)'
      SET_TO TYPE = 1
    -> Sorter_2
    -> FeatureMerger_6 [SUPPLIER]
UUIDGenerator_7
    UUID_ATTR = _uuid
    -> Counter_2
Counter_2
    CNT_ATTR = _count
    DOMAIN = @Value(cityobjectid)
    SCOPE = Global
    START = 1
    -> AttributeCreator_6
AttributeCreator_6
    ATTR_TABLE:
      SET_TO UUID = UUID_@Value(_uuid)
      SET_TO SQL = INSERT INTO citydb.surface_geometry("id", "gmlid", "parent_id", "root_id", "is_solid", "is_composite", "is_triangulated", "is_xlink", "is_reverse", "geometry", "cityobject_id")
        SELECT nextval('surface_geometry_seq'), '@Value(gml_id_polygon)', currval('surface_geometry_seq')-1, currval('surface_geometry_seq')-1, '0', '0', '0', '1', '0', st_setsrid('@Value(_geometry_polygon)'::geometry, 3008), '@Value(cityobjectid)'
      SET_TO TYPE = 2
    -> Sorter_2
Sorter_2
    SORT_PARM = cityobjectid NUMERIC ASCENDING TYPE NUMERIC ASCENDING
    SORTED -> SQLExecutor_13 [INITIATOR]
SQLExecutor_13
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = @Value(SQL)
    INITIATOR -> FeatureHolder_2
FeatureHolder_2
    -> Sampler_3

Bookmark: Writing WallSurface to thematic_surface
Sampler_3
    RATE = 1
    SAMPLE_MODE = No
    SAMPLE_TYPE_LONG = First N Features
    SAMPLED -> SQLExecutor_14 [INITIATOR]
SQLExecutor_14
    COMBINE_ATTRS = Result Attributes Only
    COMBINE_GEOM = Initiator Geometry Only
    DATASET = postgres
    EXPOSED_ATTRIBUTE_LIST = lod2multisurfaceid,gmlid,cityobject_id
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      select root_id as lod2multisurfaceid, gmlid, cityobject_id as cityobjectid
      from surface_geometry
    RESULT -> FeatureMerger_6 [REQUESTOR]
FeatureMerger_6
    ATTR_ACCUM_MODE = Merge Supplier
    ATTR_CONFLICT_RES = Use Requestor
    IGNORE_NULLS = No
    JOIN_KEYS = @Value(gmlid) @Value(gml_id) AUTO
    MERGE_TYPE = Attributes Only
    PROCESS_DUPS = NO
    REJECT_NULL_MISSING_KEYS = No
    SUPPLIERS_FIRST = No
    MERGED -> AttributeCreator_9
AttributeCreator_9
    ATTR_TABLE = SET_TO mergeid = 1
    -> FeatureMerger_9 [REQUESTOR]
FeatureMerger_9
    ATTR_ACCUM_MODE = Merge Supplier
    ATTR_CONFLICT_RES = Use Requestor
    IGNORE_NULLS = No
    JOIN_KEYS = @Value(mergeid) @Value(mergeid) AUTO
    MERGE_TYPE = Attributes Only
    PROCESS_DUPS = NO
    REJECT_NULL_MISSING_KEYS = No
    SUPPLIERS_FIRST = No
    MERGED -> SQLExecutor_15 [INITIATOR]
SQLExecutor_15
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.thematic_surface("id", "objectclass_id", "building_id", "lod2_multi_surface_id")
      SELECT '@Value(cityobjectid)', '34', '@Value(maxid)', '@Value(lod2multisurfaceid)'
    INITIATOR -> FeatureHolder_5

Bookmark: Writing RoofSurface to cityobject and storing cityobjectid and gmlid for processing
FeatureReader_2
    ATTRIBUTES = Building,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_class,citygml_class_codeSpace,citygml_function{},citygml_function{}.codeSpace,citygml_usage{},citygml_usage{}.codeSpace,citygml_year_of_construction,citygml_year_of_demolition,citygml_roof_type,citygml_roof_type_codeSpace,citygml_measured_height,citygml_measured_height_units,citygml_storeys_above_ground,citygml_storeys_below_ground,citygml_storey_heights_above_ground,citygml_storey_heights_above_ground_units,citygml_storey_heights_below_ground,citygml_storey_heights_below_ground_units,citygml_outer_building_installation{}.xlink_href,citygml_interior_building_installation{}.xlink_href,citygml_bounded_by{}.xlink_href,citygml_level_of_detail{},citygml_interior_room{}.xlink_href,citygml_consists_of_building_part{}.xlink_href,citygml_address{}.xlink_href,fme_geometry{0},fme_geometry{1},fme_geometry{2},fme_geometry{3},fme_geometry{4},fme_geometry{5},fme_geometry{6},fme_geometry{7}",CityModel,"gml_id,citygml_target_uri,gml_description,gml_name,citygml_city_object_member{}.xlink_href,citygml_appearance_member{}.xlink_href,gml_feature_member{}.xlink_href,fme_geometry{0}",GroundSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}",RoofSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}",WallSurface,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,citygml_level_of_detail{},citygml_opening{}.xlink_href,fme_geometry{0},fme_geometry{1},fme_geometry{2},fme_geometry{3},fme_geometry{4},fme_geometry{5},fme_geometry{6},fme_geometry{7}"
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = C:\Users\tomben1\OneDrive - Malmö stad\Documents\Master_thesis\Script\CityGML_LOD2\output_script\kanaan_lod2.gml
    FEATURETYPES = RoofSurface
    FORMAT = CITYGML
    INTERACT = <No Spatial Filter>
    OUTPUT_FEATURES_DISPLAY = Schema and Data Features
    RoofSurface -> Aggregator_7
    RoofSurface -> GeometryPartExtractor_4
Aggregator_7
    ACCUM_ATTRS_NAME = Use Attributes From One Feature
    AGGREGATE_TYPE = Homogeneous Collection (If Possible)
    GROUP_BY = gml_id
    MODE = Geometry - Assemble One Level
    SEP = ,
    AGGREGATE -> GeometryExtractor_8
GeometryExtractor_8
    ATTR = _geometry_bbox
    KIND_LONG = OGC Well Known Text
    OGCVERSION = 1.2
    OGC_WKT_PRECISION_DISPLAY = 64-bit
    PREFER_POLYGON_OVER_SURFACE = No
    REMOVE_GEOMETRY = Yes
    -> SQLExecutor_16 [INITIATOR]
SQLExecutor_16
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.cityobject("objectclass_id", "gmlid", "envelope", "updating_person")
      SELECT '33', '@Value(gml_id)', citydb.box2envelope(st_3dextent('@Value(_geometry_bbox)')),'Tom_Bendiksen'
    INITIATOR -> SQLExecutor_17 [INITIATOR]
SQLExecutor_17
    COMBINE_ATTRS = Result Attributes Only
    COMBINE_GEOM = Initiator Geometry Only
    DATASET = postgres
    EXPOSED_ATTRIBUTE_LIST = cityobjectid,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as cityobjectid, '@Value(gml_id)' as gmlid
      FROM citydb.cityobject
      WHERE cityobject.gmlid = '@Value(gml_id)'
    RESULT -> FeatureMerger_10 [SUPPLIER]
GeometryPartExtractor_4
    GQUERY:
      for $geom in //geometry
      where $geom/@fme_geometry_type = 'IFMEFace'
      return number($geom/@fme_id)
    EXTRACTED -> GeometryPropertyExtractor_4
GeometryPropertyExtractor_4
    EXTRACTTYPE_PARAM = Traits
    GQUERY:
      for $geom in //geometry
      where $geom/@fme_geometry_type = 'IFMEFace'
      return number($geom/@fme_id)
    PREFIX_EXTRACTED_TRAITS = Yes
    TRAIT_ATTR_LIST = gml_id,No
    EXTRACTED -> AttributeExposer_4
AttributeExposer_4
    ATTR_LIST = surfaceMember.gml_id
    -> AttributeRenamer_4
AttributeRenamer_4
    ATTR_TABLE = RENAME_SET_DEFAULT surfaceMember.gml_id > gml_id_polygon
    -> GeometryCoercer_4
GeometryCoercer_4
    GQUERY:
      for $geom in //geometry
      where $geom/count(parent::geometry) = 0
      return number($geom/@fme_id)
    KIND = fme_polygon
    COERCED -> GeometryExtractor_9
GeometryExtractor_9
    ATTR = _geometry_polygon
    KIND_LONG = OGC Well Known Text
    OGCVERSION = 1.2
    OGC_WKT_PRECISION_DISPLAY = 64-bit
    PREFER_POLYGON_OVER_SURFACE = No
    REMOVE_GEOMETRY = No
    -> FeatureMerger_10 [REQUESTOR]
FeatureMerger_10
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> Aggregator_3
    MERGED -> Aggregator_6

Bookmark: Writing RoofSurface to surface_geometry
Aggregator_3
    ACCUM_ATTRS_NAME = Use Attributes From One Feature
    AGGREGATE_TYPE = Homogeneous Collection (If Possible)
    GROUP_BY = gml_id
    MODE = Geometry - Assemble One Level
    SEP = ,
    AGGREGATE -> UUIDGenerator_8
UUIDGenerator_8
    UUID_ATTR = _uuid
    -> AttributeCreator_8
AttributeCreator_8
    ATTR_TABLE:
      SET_TO UUID = UUID_@Value(_uuid)
      SET_TO SQL = INSERT INTO citydb.surface_geometry("id", "gmlid", "parent_id", "root_id", "is_solid", "is_composite", "is_triangulated", "is_xlink", "is_reverse", "cityobject_id")
        SELECT nextval('surface_geometry_seq'), '@Value(gml_id)', NULL, currval('surface_geometry_seq'), '0', '0', '0', '0', '0', '@Value(cityobjectid)'
      SET_TO TYPE = 1
    -> Sorter_3
    -> FeatureMerger_11 [SUPPLIER]
UUIDGenerator_9
    UUID_ATTR = _uuid
    -> Counter_4
Counter_4
    CNT_ATTR = _count
    DOMAIN = @Value(cityobjectid)
    SCOPE = Global
    START = 1
    -> AttributeCreator_10
AttributeCreator_10
    ATTR_TABLE:
      SET_TO UUID = UUID_@Value(_uuid)
      SET_TO SQL = INSERT INTO citydb.surface_geometry("id", "gmlid", "parent_id", "root_id", "is_solid", "is_composite", "is_triangulated", "is_xlink", "is_reverse", "geometry", "cityobject_id")
        SELECT nextval('surface_geometry_seq'), '@Value(gml_id_polygon)', currval('surface_geometry_seq')-1, currval('surface_geometry_seq')-1, '0', '0', '0', '1', '0', st_setsrid('@Value(_geometry_polygon)'::geometry, 3008), '@Value(cityobjectid)'


      SET_TO TYPE = 2
    -> Sorter_3
Sorter_3
    SORT_PARM = cityobjectid NUMERIC ASCENDING TYPE NUMERIC ASCENDING
    SORTED -> SQLExecutor_18 [INITIATOR]
SQLExecutor_18
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = @Value(SQL)
    INITIATOR -> FeatureHolder_3

Bookmark: Writing RoofSurface to thematic_surface
FeatureHolder_3
    -> Sampler_4
Sampler_4
    RATE = 1
    SAMPLE_MODE = No
    SAMPLE_TYPE_LONG = First N Features
    SAMPLED -> SQLExecutor_19 [INITIATOR]
SQLExecutor_19
    COMBINE_ATTRS = Result Attributes Only
    COMBINE_GEOM = Initiator Geometry Only
    DATASET = postgres
    EXPOSED_ATTRIBUTE_LIST = lod2multisurfaceid,gmlid,cityobject_id
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      select root_id as lod2multisurfaceid, gmlid, cityobject_id as cityobjectid
      from surface_geometry
    RESULT -> FeatureMerger_11 [REQUESTOR]
FeatureMerger_11
    ATTR_ACCUM_MODE = Merge Supplier
    ATTR_CONFLICT_RES = Use Requestor
    IGNORE_NULLS = No
    JOIN_KEYS = @Value(gmlid) @Value(gml_id) AUTO
    MERGE_TYPE = Attributes Only
    PROCESS_DUPS = NO
    REJECT_NULL_MISSING_KEYS = No
    SUPPLIERS_FIRST = No
    MERGED -> AttributeCreator_11
AttributeCreator_11
    ATTR_TABLE = SET_TO mergeid = 1
    -> FeatureMerger_12 [REQUESTOR]
FeatureMerger_12
    ATTR_ACCUM_MODE = Merge Supplier
    ATTR_CONFLICT_RES = Use Requestor
    IGNORE_NULLS = No
    JOIN_KEYS = @Value(mergeid) @Value(mergeid) AUTO
    MERGE_TYPE = Attributes Only
    PROCESS_DUPS = NO
    REJECT_NULL_MISSING_KEYS = No
    SUPPLIERS_FIRST = No
    MERGED -> SQLExecutor_20 [INITIATOR]
SQLExecutor_20
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.thematic_surface("id", "objectclass_id", "building_id", "lod2_multi_surface_id")
      SELECT '@Value(cityobjectid)', '33', '@Value(maxid)', '@Value(lod2multisurfaceid)'
