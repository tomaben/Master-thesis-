FME workspace Import_LOD1 (2020.2).fmw

Parameters:
- SourceDataset_CITYGML_21 = C:\Users\tomben1\OneDrive - Malmö stad\Documents\Master_thesis\Script\CityGML_LOD1\output_script\Multihuset_LOD1.3.gml   # Source CityGML File(s)
- SourceDataset_CITYGML = C:\Users\tomben1\OneDrive - Malmö stad\Documents\Master_thesis\Script\CityGML_LOD1\output_script\Kristallen_LOD1.3.gml   # Source CityGML File(s)
- SourceDataset_CITYGML_13 = C:\Users\tomben1\OneDrive - Malmö stad\Documents\Master_thesis\Script\CityGML_LOD1\output_script\Kristallen_LOD1.2.gml   # Source CityGML File(s)
- SourceDataset_CITYGML_17 = C:\Users\tomben1\OneDrive - Malmö stad\Documents\Master_thesis\Script\CityGML_LOD1\output_script\Kristallen_LOD1.1.gml   # Source CityGML File(s)
- SourceDataset_CITYGML_15 = C:\Users\tomben1\OneDrive - Malmö stad\Documents\Master_thesis\Script\CityGML_LOD1\output_script\Multihuset_LOD1.2.gml   # Source CityGML File(s)
- SourceDataset_CITYGML_19 = C:\Users\tomben1\OneDrive - Malmö stad\Documents\Master_thesis\Script\CityGML_LOD1\output_script\Multihuset_LOD1.1.gml   # Source CityGML File(s)
- SourceDataset_CITYGML_12 = C:\Users\tomben1\OneDrive - Malmö stad\Documents\Master_thesis\Script\CityGML_LOD1\output_script\Undervisningshuset_LOD1.3.gml   # Source CityGML File(s)
- SourceDataset_CITYGML_14 = C:\Users\tomben1\OneDrive - Malmö stad\Documents\Master_thesis\Script\CityGML_LOD1\output_script\Undervisningshuset_LOD1.2.gml   # Source CityGML File(s)
- SourceDataset_CITYGML_16 = C:\Users\tomben1\OneDrive - Malmö stad\Documents\Master_thesis\Script\CityGML_LOD1\output_script\Undervisningshuset_LOD1.1.gml   # Source CityGML File(s)
- SourceDataset_CITYGML_18 = C:\Users\tomben1\OneDrive - Malmö stad\Documents\Master_thesis\Script\CityGML_LOD1\output_script\Kanaans_LOD1.1.gml   # Source CityGML File(s)
- SourceDataset_CITYGML_20 = C:\Users\tomben1\OneDrive - Malmö stad\Documents\Master_thesis\Script\CityGML_LOD1\output_script\Kanaans_LOD1.2.gml   # Source CityGML File(s)

Readers:
- CITYGML_1: CITYGML from $(SourceDataset_CITYGML_21)
- CITYGML_2: CITYGML from $(SourceDataset_CITYGML)
- CITYGML_3: CITYGML from $(SourceDataset_CITYGML_13)
- CITYGML_4: CITYGML from $(SourceDataset_CITYGML_17)
- CITYGML_5: CITYGML from $(SourceDataset_CITYGML_15)
- CITYGML_6: CITYGML from $(SourceDataset_CITYGML_19)
- CITYGML_7: CITYGML from $(SourceDataset_CITYGML_12)
- CITYGML_8: CITYGML from $(SourceDataset_CITYGML_14)
- CITYGML_9: CITYGML from $(SourceDataset_CITYGML_16)
- CITYGML_10: CITYGML from $(SourceDataset_CITYGML_18)
- CITYGML_11: CITYGML from $(SourceDataset_CITYGML_20)

GeometryExtractor
    ATTR = _geometry_bbox
    KIND_LONG = OGC Well Known Text
    OGCVERSION = 1.2
    OGC_WKT_PRECISION_DISPLAY = 64-bit
    PREFER_POLYGON_OVER_SURFACE = No
    REMOVE_GEOMETRY = Yes
    -> SQLExecutor [INITIATOR]
SQLExecutor
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.cityobject("objectclass_id", "gmlid", "envelope", "updating_person")
      SELECT '26', '@Value(gml_id)', citydb.box2envelope(st_3dextent('@Value(_geometry_bbox)')),'Tom_Bendiksen'
      FROM citydb.cityobject
    INITIATOR -> SQLExecutor_2 [INITIATOR]
SQLExecutor_2
    COMBINE_ATTRS = Result Attributes Only
    COMBINE_GEOM = Initiator Geometry Only
    DATASET = postgres
    EXPOSED_ATTRIBUTE_LIST = maxid,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as maxid, '@Value(gml_id)' as gmlid
      FROM citydb.cityobject
      order by maxid desc
      limit 1
    RESULT -> FeatureMerger [SUPPLIER]
    RESULT -> FeatureMerger_2 [SUPPLIER]
Note: Slår sammen geometrier for lagring i solid_geometry som finnes i surface_geometry
Aggregator
    ACCUM_ATTRS_NAME = Use Attributes From One Feature
    AGGREGATE_TYPE = Homogeneous Collection (If Possible)
    GROUP_BY = gml_id
    MODE = Geometry - Assemble One Level
    SEP = ,
    AGGREGATE -> GeometryExtractor_3
Note: Endrer geometrier til OGC WKT
GeometryExtractor_3
    ATTR = _geometry_solid
    KIND_LONG = OGC Well Known Text
    OGCVERSION = 1.2
    OGC_WKT_PRECISION_DISPLAY = 64-bit
    PREFER_POLYGON_OVER_SURFACE = No
    REMOVE_GEOMETRY = No
    -> StringReplacer
Note: Erstatter multipolygon med polyhedralsurface for å bruke i st_makesolid
StringReplacer
    CASE = NO
    FIND_TEXT = MULTIPOLYGON
    NO_MATCH = _FME_NO_OP_
    REGEXP = NO
    REPLACE_TEXT = POLYHEDRALSURFACE
    SRC_ATTRS = _geometry_solid
    -> FeatureMerger [REQUESTOR]
FeatureMerger
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> UUIDGenerator
    MERGED -> UUIDGenerator_2
UUIDGenerator
    UUID_ATTR = _uuid
    -> AttributeCreator
AttributeCreator
    ATTR_TABLE:
      SET_TO UUID = UUID_@Value(_uuid)
      SET_TO SQL = INSERT INTO citydb.surface_geometry("id", "gmlid", "parent_id", "root_id", "is_solid", "is_composite", "is_triangulated", "is_xlink", "is_reverse", "solid_geometry", "cityobject_id")
        SELECT nextval('surface_geometry_seq'), '@Value(UUID)', NULL, currval('surface_geometry_seq'), '1', '0', '0', '0', '0', st_setsrid(st_makesolid('@Value(_geometry_solid)'), 3008), '@Value(maxid)'
      SET_TO TYPE = 1
    -> Sorter
    -> FeatureMerger_3 [SUPPLIER]
UUIDGenerator_2
    UUID_ATTR = _uuid
    -> AttributeCreator_2
AttributeCreator_2
    ATTR_TABLE:
      SET_TO UUID = UUID_@Value(_uuid)
      SET_TO SQL = INSERT INTO citydb.surface_geometry("id", "gmlid", "parent_id", "root_id", "is_solid", "is_composite", "is_triangulated", "is_xlink", "is_reverse", "cityobject_id")
        SELECT nextval('surface_geometry_seq'), '@Value(UUID)', currval('surface_geometry_seq')-1, currval('surface_geometry_seq')-1, '0', '1', '0', '0', '0', '@Value(maxid)'
      SET_TO TYPE = 2
    -> Sorter
GeometryExtractor_2
    ATTR = _geometry_polygon
    KIND_LONG = OGC Well Known Text
    OGCVERSION = 1.2
    OGC_WKT_PRECISION_DISPLAY = 64-bit
    PREFER_POLYGON_OVER_SURFACE = No
    REMOVE_GEOMETRY = No
    -> FeatureMerger_2 [REQUESTOR]
FeatureMerger_2
    ATTR_ACCUM_MODE = Merge Supplier
    ATTR_CONFLICT_RES = Use Requestor
    IGNORE_NULLS = No
    JOIN_KEYS = @Value(gml_id) @Value(gmlid) AUTO
    MERGE_TYPE = Attributes Only
    PROCESS_DUPS = NO
    REJECT_NULL_MISSING_KEYS = No
    SUPPLIERS_FIRST = No
    MERGED -> UUIDGenerator_3
UUIDGenerator_3
    UUID_ATTR = _uuid
    -> Counter
Counter
    CNT_ATTR = _count
    DOMAIN = @Value(maxid)
    SCOPE = Global
    START = 2
    -> AttributeCreator_3
AttributeCreator_3
    ATTR_TABLE:
      SET_TO UUID = UUID_@Value(_uuid)
      SET_TO SQL = insert into citydb.surface_geometry ("id", "gmlid", "parent_id", "root_id", "is_solid", "is_composite", "is_triangulated", "is_xlink", "is_reverse", "geometry", "cityobject_id")
        select nextval('surface_geometry_seq'), '@Value(UUID)', currval('surface_geometry_seq')-(@Value(_count)-1),  currval('surface_geometry_seq')-@Value(_count), '0', '0', '0', '0', '0', st_setsrid('@Value(_geometry_polygon)'::geometry, 3008), @Value(maxid)
      SET_TO TYPE = 3
    -> Sorter
Sorter
    SORT_PARM = maxid NUMERIC ASCENDING TYPE NUMERIC ASCENDING _count NUMERIC ASCENDING
    SORTED -> SQLExecutor_3 [INITIATOR]
SQLExecutor_3
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = @Value(SQL)
    INITIATOR -> FeatureHolder
FeatureHolder
    -> Sampler
Sampler
    RATE = 1
    SAMPLE_MODE = No
    SAMPLE_TYPE_LONG = First N Features
    SAMPLED -> SQLExecutor_4 [INITIATOR]
SQLExecutor_4
    COMBINE_ATTRS = Result Attributes Only
    COMBINE_GEOM = Initiator Geometry Only
    DATASET = postgres
    EXPOSED_ATTRIBUTE_LIST = id,gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT = select id, gmlid from surface_geometry
    RESULT -> FeatureMerger_3 [REQUESTOR]
FeatureMerger_3
    ATTR_ACCUM_MODE = Merge Supplier
    ATTR_CONFLICT_RES = Use Requestor
    IGNORE_NULLS = No
    JOIN_KEYS = @Value(gmlid) @Value(UUID) AUTO
    MERGE_TYPE = Attributes Only
    PROCESS_DUPS = NO
    REJECT_NULL_MISSING_KEYS = No
    SUPPLIERS_FIRST = No
    MERGED -> SQLExecutor_5 [INITIATOR]
SQLExecutor_5
    COMBINE_ATTRS = Result Attributes Only
    COMBINE_GEOM = Initiator Geometry Only
    DATASET = postgres
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      INSERT INTO citydb.building("id", "objectclass_id", "building_root_id", "lod1_solid_id")
      SELECT @Value(maxid), '26', @Value(maxid), @Value(id)

Bookmark: Multihuset LOD 1.3
Building (reader CITYGML_1)
    attributes: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

Bookmark: Kristallen LOD 1.3
Building (reader CITYGML_2)
    attributes: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

Bookmark: Kristallen LOD 1.2
Building (reader CITYGML_3)
    attributes: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

Bookmark: Kristallen LOD 1.1
Building (reader CITYGML_4)
    attributes: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

Bookmark: Multihuset LOD 1.2
Building (reader CITYGML_5)
    attributes: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

Bookmark: Multihuset LOD 1.1
Building (reader CITYGML_6)
    attributes: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

Bookmark: Undervisningshuset LOD 1.3
Building (reader CITYGML_7)
    attributes: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

Bookmark: Undervisningshuset LOD 1.2
Building (reader CITYGML_8)
    attributes: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

Bookmark: Undervisningshuset LOD 1.1
Building (reader CITYGML_9)
    attributes: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

Bookmark: Kanaans Cafe LOD 1.1
Building (reader CITYGML_10)
    attributes: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

Bookmark: Kanaans Cafe LOD 1.2
Building (reader CITYGML_11)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
    -> GeometryExtractor
    -> GeometryPartExtractor

Bookmark: Bryter opp soliden til polygoner for lagring i surface_geometry
GeometryPartExtractor
    GQUERY:
      for $geom in //geometry
      where $geom/@fme_geometry_type = 'IFMEFace'
      return number($geom/@fme_id)
    EXTRACTED -> GeometryCoercer
GeometryCoercer
    GQUERY:
      for $geom in //geometry
      where $geom/count(parent::geometry) = 0
      return number($geom/@fme_id)
    KIND = fme_polygon
    COERCED -> AttributeKeeper
AttributeKeeper
    CREATE_BULK_MODE_FEATURES = NO
    KEEP_ATTRS = gml_id
    -> GeometryExtractor_2
    -> Aggregator
