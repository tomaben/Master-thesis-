FME workspace KristallenNSLOD02_to_citygmllod1.2.fmw

Parameters:
- DestDataset_CITYGML = $(FME_MF_DIR)output_script\Kristallen_LOD1.2.gml   # Destination CityGML Document
- SourceDataset_GEOJSON_3 = C:\Users\tomben1\OneDrive - Malmö stad\Documents\Master_thesis\Data\Kristallen_Lund\Kristallen_NS_LOD_02.json   # Source GeoJSON File or URL

Readers:
- GEOJSON_2: GEOJSON from $(SourceDataset_GEOJSON_3) in EPSG:3008

Writers:
- CITYGML_1: CITYGML to $(DestDataset_CITYGML) in EPSG:3008

Kristallen_NS_LOD_02_footprint [GEOJSON] (reader GEOJSON_2)
    attributes: GeoNS_LOD0_planläge string, Geometriredovisning_Ytgeometri_Koordinatsystem_i_plan string, Geometriredovisning_Ytgeometri_Höjdsystem string, Geometriredovisning_lägesbestämningsmeetod_i_plan_konvertering_variant string, Geometriredovisning_lägesbestämningsmeetod_i_höjd_konvertering_variant string, Geometriredovisning_följer_mätanvisningar string, Variant_NS_LOD string
    -> Extruder_2
Extruder_2
    DIRECTION = Auto
    DISTANCE = 30
    EXTRUDED -> Clipper [CLIPPEE]
Kristallen_NS_LOD_02_roof [GEOJSON] (reader GEOJSON_2)
    attributes: GeoNS_LOD0_planläge string, GeoNS_LOD0_höjdläge string, Geometriredovisning_Ytgeometri_Koordinatsystem_i_plan string, Geometriredovisning_Ytgeometri_Höjdsystem string, Geometriredovisning_lägesbestämningsmeetod_i_plan_konvertering_variant string, Geometriredovisning_lägesbestämningsmeetod_i_höjd_konvertering_variant string, Geometriredovisning_följer_mätanvisningar string, Variant_NS_LOD string
    -> Extruder_3
Extruder_3
    DIRECTION = Auto
    DISTANCE = -30
    EXTRUDED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> GeometryValidator_2
GeometryValidator_2
    ISSUE_ATTR_NAME = _issues
    PRESETS = Custom
    REPAIR = Yes
    RULES = PLANAR_SURFACE CHECK_AREA]DO_NOT_CHECK_AREA]TOLERANCE_MODE]AUTO]TOLERANCE]0.0]ANGULAR_TOLERANCE_MODE]Automatic]ANGULAR_TOLERANCE]0.0]FME_CONTROLLER_QUERY_FILE]transformers/dependencies/geometryvalidator/PLANAR_SURFACE.fme
    SUMMARY = Detailed
    PASSED -> Aggregator
    REPAIRED -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> AttributeCreator
AttributeCreator
    ATTR_TABLE:
      SET_TO gml_id = gml_@UUID()
      SET_TO citygml_level_of_detail = 1
    -> AttributeKeeper
AttributeKeeper
    CREATE_BULK_MODE_FEATURES = NO
    KEEP_ATTRS = citygml_level_of_detail,gml_id
    -> CityGMLGeometrySetter
CityGMLGeometrySetter
    GEOM = lod1Solid
    ROLE = cityObjectMember
    -> Building (writer CITYGML_1)
Building (writer CITYGML_1)
    attributes: citygml_feature_role xml_char(200)
Orientor
    FLIP_APPEARANCES_CHOICE = Yes
    KIND = REVERSE
