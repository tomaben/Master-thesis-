FME workspace KanaansNSLOD02_to_citygmllod1.2.fmw

Parameters:
- DestDataset_CITYGML = $(FME_MF_DIR)output_script\Kanaans_LOD1.2.gml   # Destination CityGML Document
- SourceDataset_GEOJSON = C:\Users\tomben1\OneDrive - Malmö stad\Documents\Master_thesis\Data\Kanaans_Cafe_Stockholm\Kanaan_NS_LOD_02.json   # Source GeoJSON File or URL

Readers:
- GEOJSON_2: GEOJSON from $(SourceDataset_GEOJSON) in EPSG:3008

Writers:
- CITYGML_1: CITYGML to $(DestDataset_CITYGML) in EPSG:3008

Kanaan_NS_LOD_02_footprint (reader GEOJSON_2)
    attributes: BYD_andamal string, BYD_absoluthojd_hojdlage_1 string, BYD_absoluthojd_hojdvarde_1 float, BYD_absoluthojd_hojdlage_2 string, BYD_absoluthojd_hojdvarde_2 float, BYD_absoluthojd_hojdlage_3 string, BYD_absoluthojd_hojdvarde_3 float, BYD_G_NS_LOD0_Hojdlage string, BYD_G_NS_LOD0_Planlage string, BYD_G_NS_LOD0_NS_LOD string
    -> Extruder_2
Extruder_2
    DIRECTION = Auto
    DISTANCE = 6.89
    EXTRUDED -> GeometryValidator_2
GeometryValidator_2
    ISSUE_ATTR_NAME = _issues
    PRESETS = Custom
    REPAIR = Yes
    RULES = PLANAR_SURFACE CHECK_AREA]DO_NOT_CHECK_AREA]TOLERANCE_MODE]AUTO]TOLERANCE]0.0]ANGULAR_TOLERANCE_MODE]Automatic]ANGULAR_TOLERANCE]0.0]FME_CONTROLLER_QUERY_FILE]transformers/dependencies/geometryvalidator/PLANAR_SURFACE.fme
    SUMMARY = Detailed
    PASSED -> Aggregator
    REPAIRED -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> AttributeCreator
AttributeCreator
    ATTR_TABLE:
      SET_TO gml_id = gml_@UUID()
      SET_TO citygml_level_of_detail = 1
    -> AttributeKeeper
AttributeKeeper
    CREATE_BULK_MODE_FEATURES = NO
    KEEP_ATTRS = citygml_level_of_detail,gml_id
    -> CityGMLGeometrySetter
CityGMLGeometrySetter
    GEOM = lod1Solid
    ROLE = cityObjectMember
    -> Building (writer CITYGML_1)
Building (writer CITYGML_1)
    attributes: citygml_feature_role xml_char(200)
