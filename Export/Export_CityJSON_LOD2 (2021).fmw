FME workspace Export_CityJSON_LOD2 (2021).fmw

Parameters:
- DestDataset_CITYJSON =
- gml_id_export =

Writers:
- CITYJSON_1: CITYJSON to $(DestDataset_CITYJSON)

Starter
    -> SQLExecutor [INITIATOR]
SQLExecutor
    COMBINE_ATTRS = Result Attributes Only
    COMBINE_GEOM = Initiator Geometry Only
    DATASET = postgres
    EXPOSED_ATTRIBUTE_LIST = cityobjectid
    FORMAT = POSTGIS
    POSTGIS_NAMED_CONNECTION = postgres
    SQL_STATEMENT:
      SELECT id as cityobjectid
      FROM citydb.cityobject
      WHERE gmlid = '$(gml_id_export)'
    RESULT -> SQLExecutor_2 [INITIATOR]
SQLExecutor_2
    COMBINE_ATTRS = Result Attributes Only
    COMBINE_GEOM = Initiator Geometry Only
    DATASET = postgres
    EXPOSED_ATTRIBUTE_LIST = solid
    FORMAT = POSTGRES
    POSTGRES_CREATE_FEATURE_TABLES_FROM_DATA = Yes
    POSTGRES_NAMED_CONNECTION = postgres
    POSTGRES_QUERY_FEATURE_TYPES_FOR_MERGE_FILTERS = Yes
    POSTGRES_READ_TIME_WITH_TIMEZONE = Yes
    SQL_STATEMENT:
      SELECT solid_geometry as solid
      FROM citydb.surface_geometry
      WHERE cityobject_id = '@Value(cityobjectid)'
    RESULT -> GeometryReplacer
GeometryReplacer
    ELLIPSOID_NAME = WGS84
    KIND_LONG = Hex Encoded OGC Well Known Binary
    LETTERING = WGS84
    MSSQL_FORMAT_CHOICE = Geometry
    OGC_WKT_PRECISION_DISPLAY = 64-bit
    OUTPUT_POINT_DISPLAY = Point
    REMOVE_ATTRIBUTE = Yes
    SOURCE = @Value(solid)
    SRS_AXIS_ORDER_DISPLAY = Automatic
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> FaceReplacer
FaceReplacer
    ANGULAR_TOLERANCE_CHOICE = Automatic
    THICKNESS_TOLERANCE_CHOICE = Ignore
    -> GeometryValidator
GeometryValidator
    ISSUE_ATTR_NAME = _issues
    PRESETS = Custom
    REPAIR = Yes
    RULES = "MISSING_VERTEX_NORMALS "
    SUMMARY = Detailed
    PASSED -> GeometryPropertySetter
    REPAIRED -> GeometryPropertySetter
GeometryPropertySetter
    CNT_ATTR = _count
    DOMAIN = counter
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor_2
GeometryPartExtractor_2
    GQUERY:
      for $geom in //geometry
      where $geom/@fme_geometry_type = 'IFMEFace'
      return number($geom/@fme_id)
    EXTRACTED -> MeasureExtractor
MeasureExtractor
    GEOM_TYPE = Individual Vertex by Index
    INDEX = 0
    MEASURE_ATTR = _normal_z
    MEASURE_NAME = fme_vertex_normal_z
    -> TestFilter_2
TestFilter_2
    DEFAULT_VALUE = WallSurface
    TEST_LIST = "BOOL_OP,OR,COMPOSITE_TEST,""""""1"""""",TEST_CLAUSE,TEST @Value(_normal_z) = -1",GroundSurface,"BOOL_OP,OR,COMPOSITE_TEST,""""""1"""""",TEST_CLAUSE,TEST @Value(_normal_z) > 0.5",RoofSurface
    GroundSurface -> GeometryPropertySetter_2
    RoofSurface -> GeometryPropertySetter_3
    WallSurface -> GeometryPropertySetter_4
GeometryPropertySetter_2
    GEOM_NAME_FIELD = GroundSurface
    GQUERY:
      for $geom in //geometry
      where $geom/@fme_geometry_type = 'IFMEFace'
      return number($geom/@fme_id)
    OVERWRITE_CHOICE = Yes
    SETTYPE_PARAM = Geometry Name
    SET -> Aggregator
GeometryPropertySetter_3
    GEOM_NAME_FIELD = RoofSurface
    GQUERY:
      for $geom in //geometry
      where $geom/@fme_geometry_type = 'IFMEFace'
      return number($geom/@fme_id)
    OVERWRITE_CHOICE = Yes
    SETTYPE_PARAM = Geometry Name
    SET -> Aggregator
GeometryPropertySetter_4
    GEOM_NAME_FIELD = WallSurface
    GQUERY:
      for $geom in //geometry
      where $geom/@fme_geometry_type = 'IFMEFace'
      return number($geom/@fme_id)
    OVERWRITE_CHOICE = Yes
    SETTYPE_PARAM = Geometry Name
    SET -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> GeometryPropertyRemover
GeometryPropertyRemover
    GQUERY:
      for $geom in //geometry
      where $geom/@fme_geometry_type = 'IFMEFace'
      return number($geom/@fme_id)
    REGEX_FILTER = _count
    REMOVETYPE_PARAM = Traits
    REMOVE_ALL = No
    REMOVED -> AttributeCreator
AttributeCreator
    ATTR_TABLE:
      SET_TO fid = $(gml_id_export)
      SET_TO cityjson_lod = 2
    -> SubstringExtractor
SubstringExtractor
    END = -1
    RESULT_ATTR = fid
    SRC_STRING = @Value(fid)
    START = 3
    -> AttributeManager
AttributeManager
    ATTR_TABLE = SET_TO fid = fid@Value(fid)
    -> AttributeKeeper
AttributeKeeper
    CREATE_BULK_MODE_FEATURES = NO
    KEEP_ATTRS = cityjson_lod,fid
    -> Building (writer CITYJSON_1)
Building (writer CITYJSON_1)
    attributes: fid string, class string, creationDate string, function string, terminationDate string, usage string, geographicalExtent{} real64, address.CountryName string, address.LocalityName string, address.PostalCode string, address.ThoroughfareName string, address.ThoroughfareNumber string, address.location.boundaries{} int32, address.location.lod real64, measuredHeight real64, roofType string, storeyHeightsAboveGround{} real64, storeyHeightsBelowGround{} real64, storeysAboveGround int32, storeysBelowGround int32, yearOfConstruction int32, yearOfDemolition int32

FME custom transformer Starter
This transformer is intended to start a workspace branch without the use of the creator transformer. This will end up without additional attributes (_creation_instance) at the end of the workspace.

Creator
    GEOMTYPE = Geometry Object
    NUM = 1
    CREATED -> Output (output)
Output (output)
