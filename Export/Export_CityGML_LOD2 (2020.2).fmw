FME workspace Export_CityGML_LOD2 (2020.2).fmw

Parameters:
- gml_id_export = gml_d54735ff-0803-41d2-905c-2972490b6cf7   # gml_id export
- DestDataset_CITYGML_3 = $(FME_MF_DIR)Output_script\Undervisningshuset_LOD_2.0.gml   # Destination CityGML Document

Writers:
- CITYGML_1: CITYGML to $(DestDataset_CITYGML_3) in SWEREF-99-13-30

Starter
    -> SQLExecutor [INITIATOR]
FeatureMerger
    ATTR_ACCUM_MODE = Merge Supplier
    ATTR_CONFLICT_RES = Use Requestor
    IGNORE_NULLS = No
    JOIN_KEYS = @Value(cityobject_id) @Value(cityobjectid) AUTO
    MERGE_TYPE = Attributes Only
    PROCESS_DUPS = NO
    REJECT_NULL_MISSING_KEYS = No
    SUPPLIERS_FIRST = No
    UNMERGED_REQUESTOR -> SQLExecutor_5 [INITIATOR]
AttributeCreator_12
    ATTR_TABLE = SET_TO polygon_id = @Value(gml_id)_polygon
    -> GeometryReplacer
GeometryReplacer
    ELLIPSOID_NAME = WGS84
    KIND_LONG = Hex Encoded OGC Well Known Binary
    LETTERING = WGS84
    MSSQL_FORMAT_CHOICE = Geometry
    OGC_WKT_PRECISION_DISPLAY = 64-bit
    OUTPUT_POINT_DISPLAY = Point
    REMOVE_ATTRIBUTE = Yes
    SOURCE = @Value(geometry)
    SRS_AXIS_ORDER_DISPLAY = Automatic
    -> FaceReplacer
FaceReplacer
    ANGULAR_TOLERANCE_CHOICE = Automatic
    THICKNESS_TOLERANCE_CHOICE = Ignore
    -> GeometryPropertySetter_4
GeometryPropertySetter_4
    GQUERY:
      for $geom in //geometry
      where $geom/@fme_geometry_type = 'IFMEFace'
      return number($geom/@fme_id)
    OVERWRITE_CHOICE = Yes
    REMOVE_ATTRIBUTE = No
    SETTYPE_PARAM = Traits From Attributes
    SRC_ATTRS = polygon_id
    SET -> GeometryPropertyRenamer_2
GeometryPropertyRenamer_2
    GQUERY:
      for $geom in //geometry
      where $geom/@fme_geometry_type = 'IFMEFace'
      return number($geom/@fme_id)
    PARAM_LIST = polygon_id,gml_id
    RENAMETYPE_PARAM = Traits
    RENAMED -> AttributeCreator_9
AttributeCreator_9
    ATTR_TABLE = SET_TO xlink_href = #@Value(polygon_id)
    -> GeometryPropertySetter_5
GeometryPropertySetter_5
    OVERWRITE_CHOICE = Yes
    REMOVE_ATTRIBUTE = No
    SETTYPE_PARAM = Traits From Attributes
    SRC_ATTRS = xlink_href
    SET -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> GeometryCoercer
GeometryCoercer
    GQUERY:
      for $geom in //geometry
      where $geom/count(parent::geometry) = 0
      return number($geom/@fme_id)
    KIND = fme_brep_solid
    COERCED -> GeometryValidator
GeometryValidator
    ISSUE_ATTR_NAME = _issues
    PRESETS = Custom
    REPAIR = Yes
    RULES = PLANAR_SURFACE CHECK_AREA]DO_CHECK_AREA]TOLERANCE_MODE]AUTO]TOLERANCE]<Unused>]ANGULAR_TOLERANCE_MODE]AUTO]ANGULAR_TOLERANCE]<Unused>]FME_CONTROLLER_QUERY_FILE]transformers/dependencies/geometryvalidator/PLANAR_SURFACE.fme
    SUMMARY = Detailed
    PASSED -> AttributeCreator
    REPAIRED -> AttributeCreator
AttributeCreator
    ATTR_TABLE:
      SET_TO gml_id = $(gml_id_export)
      SET_TO citygml_level_of_detail = 2
    -> AttributeKeeper
AttributeKeeper
    CREATE_BULK_MODE_FEATURES = NO
    KEEP_ATTRS = citygml_level_of_detail,gml_id
    -> CityGMLGeometrySetter
CityGMLGeometrySetter
    GEOM = lod2Solid
    ROLE = cityObjectMember
    -> Orientor
Orientor
    FLIP_APPEARANCES_CHOICE = Yes
    KIND = REVERSE
    ORIENTED -> Building (writer CITYGML_1)
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
GeometryReplacer_2
    ELLIPSOID_NAME = WGS84
    KIND_LONG = Hex Encoded OGC Well Known Binary
    LETTERING = WGS84
    MSSQL_FORMAT_CHOICE = Geometry
    OGC_WKT_PRECISION_DISPLAY = 64-bit
    OUTPUT_POINT_DISPLAY = Point
    REMOVE_ATTRIBUTE = Yes
    SOURCE = @Value(geometry)
    SRS_AXIS_ORDER_DISPLAY = Automatic
    -> FaceReplacer_2
FaceReplacer_2
    ANGULAR_TOLERANCE_CHOICE = Automatic
    THICKNESS_TOLERANCE_CHOICE = Ignore
    -> Aggregator_3
Aggregator_3
    ACCUM_ATTRS_NAME = Use Attributes From One Feature
    AGGREGATE_TYPE = Homogeneous Collection (If Possible)
    GROUP_BY = gml_id
    MODE = Geometry - Assemble One Level
    SEP = ,
    AGGREGATE -> GeometryPropertySetter_2
GeometryPropertySetter_2
    GQUERY:
      for $geom in //geometry
      where $geom/@fme_geometry_type = 'IFMEMultiSurface'
      return number($geom/@fme_id)
    OVERWRITE_CHOICE = Yes
    REMOVE_ATTRIBUTE = No
    SETTYPE_PARAM = Traits From Attributes
    SRC_ATTRS = gml_id
    SET -> AttributeCreator_10
AttributeCreator_10
    ATTR_TABLE = SET_TO polygon_id = @Value(gml_id)_polygon
    -> GeometryPropertySetter_3
GeometryPropertySetter_3
    GQUERY:
      for $geom in //geometry
      where $geom/@fme_geometry_type = 'IFMEFace'
      return number($geom/@fme_id)
    OVERWRITE_CHOICE = Yes
    REMOVE_ATTRIBUTE = No
    SETTYPE_PARAM = Traits From Attributes
    SRC_ATTRS = polygon_id
    SET -> GeometryPropertyRenamer
GeometryPropertyRenamer
    GQUERY:
      for $geom in //geometry
      where $geom/@fme_geometry_type = 'IFMEFace'
      return number($geom/@fme_id)
    PARAM_LIST = polygon_id,gml_id
    RENAMETYPE_PARAM = Traits
    RENAMED -> CityGMLGeometrySetter_3
CityGMLGeometrySetter_3
    GEOM = lod2MultiSurface
    ROLE = boundedBy
    -> GeometryPropertyRemover_3
GeometryPropertyRemover_3
    GQUERY:
      for $geom in //geometry
      where $geom/@fme_geometry_type = 'IFMEPolygon'
      return number($geom/@fme_id)
    REMOVETYPE_PARAM = Traits
    REMOVE_ALL = Yes
    REMOVED -> GeometryPropertyRemover_4
GeometryPropertyRemover_4
    GQUERY:
      for $geom in //geometry
      where $geom/@fme_geometry_type = 'IFMEMultiSurface'
      return number($geom/@fme_id)
    REGEX_FILTER = gml_id
    REMOVETYPE_PARAM = Traits
    REMOVE_ALL = No
    REMOVED -> SQLExecutor_6 [INITIATOR]
Orientor_2
    FLIP_APPEARANCES_CHOICE = Yes
    KIND = REVERSE
    ORIENTED -> TestFilter
TestFilter
    DEFAULT_VALUE = <UNFILTERED>
    TEST_LIST = "BOOL_OP,OR,COMPOSITE_TEST,""""""1"""""",TEST_CLAUSE,TEST @Value(objectclass_id) = 33",RoofSurface,"BOOL_OP,OR,COMPOSITE_TEST,""""""1"""""",TEST_CLAUSE,TEST @Value(objectclass_id) = 34",WallSurface,"BOOL_OP,OR,COMPOSITE_TEST,""""""1"""""",TEST_CLAUSE,TEST @Value(objectclass_id) = 35",GroundSurface
    RoofSurface -> RoofSurface (writer CITYGML_1)
    WallSurface -> WallSurface (writer CITYGML_1)
    GroundSurface -> GroundSurface (writer CITYGML_1)
RoofSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
WallSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
GroundSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer

Bookmark: Finding cityobject_id using input gml_id from cityobject
SQLExecutor
    COMBINE_ATTRS = Result Attributes Only
    COMBINE_GEOM = Initiator Geometry Only
    DATASET = postgres
    EXPOSED_ATTRIBUTE_LIST = cityobjectid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as cityobjectid
      FROM citydb.cityobject
      WHERE gmlid = '$(gml_id_export)'
    RESULT -> AttributeKeeper_2
    RESULT -> SQLExecutor_3 [INITIATOR]
AttributeKeeper_2
    CREATE_BULK_MODE_FEATURES = NO
    KEEP_ATTRS = cityobjectid
    -> FeatureMerger [SUPPLIER]

Bookmark: Using cityobject_id to find geometries and necessary attributes from surface_geometry
SQLExecutor_3
    COMBINE_ATTRS = Result Attributes Only
    COMBINE_GEOM = Initiator Geometry Only
    DATASET = postgres
    EXPOSED_ATTRIBUTE_LIST = gmlid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT gmlid
      FROM citydb.surface_geometry
      WHERE cityobject_id = '@Value(cityobjectid)'
    RESULT -> SQLExecutor_4 [INITIATOR]
SQLExecutor_4
    COMBINE_ATTRS = Result Attributes Only
    COMBINE_GEOM = Initiator Geometry Only
    DATASET = postgres
    EXPOSED_ATTRIBUTE_LIST = gmlid,root_id,geometry,cityobject_id
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT *
      FROM citydb.surface_geometry
      WHERE gmlid = '@Value(gmlid)'
    RESULT -> FeatureMerger [REQUESTOR]

Bookmark: Using root_id to retrieve abstract + geometries
SQLExecutor_5
    COMBINE_ATTRS = Result Attributes Only
    COMBINE_GEOM = Initiator Geometry Only
    DATASET = postgres
    EXPOSED_ATTRIBUTE_LIST = gml_id,geometry
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT gmlid as gml_id, '@Value(geometry)' as geometry
      FROM surface_geometry
      WHERE '@Value(root_id)' = root_id
    RESULT -> Matcher
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = geometry
    MATCH_STRATEGY = Match Selected Attributes
    SINGLE_MATCHED -> GeometryReplacer_2
    SINGLE_MATCHED -> AttributeCreator_12

Bookmark: Retrieving objectclass_id and setting gml_parent_id
SQLExecutor_6
    ATTR_IGNORE_NULLS = No
    COMBINE_ATTRS = Keep Initiator Attributes if Conflict
    COMBINE_GEOM = Initiator Geometry Only
    DATASET = postgres
    EXPOSED_ATTRIBUTE_LIST = objectclass_id
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT objectclass_id
      FROM citydb.cityobject
      WHERE gmlid = '@Value(gml_id)'
    RESULT -> AttributeCreator_2
AttributeCreator_2
    ATTR_TABLE = SET_TO gml_parent_id = $(gml_id_export)
    -> Orientor_2

FME custom transformer Starter
This transformer is intended to start a workspace branch without the use of the creator transformer. This will end up without additional attributes (_creation_instance) at the end of the workspace.

Creator
    GEOMTYPE = Geometry Object
    NUM = 1
    CREATED -> Output (output)
Output (output)
