FME workspace UndervisningshusetNSlod20_til_CityGML_lod2.fmw

Parameters:
- DestDataset_CITYGML_3 = $(FME_MF_DIR)output_script\undervisningshuset_lod_2.gml   # Destination CityGML Document
- SourceDataset_GEOJSON = C:\Users\tomben1\OneDrive - Malmö stad\Documents\Master_thesis\Data\Undervisningshuset_Stockholm\Undervisningshuset_NS_LOD_20.json   # Source GeoJSON File or URL

Readers:
- GEOJSON_1: GEOJSON from $(SourceDataset_GEOJSON) in SWEREF-99-13-30

Writers:
- CITYGML_1: CITYGML to $(DestDataset_CITYGML_3) in SWEREF-99-13-30

UndervisningsHuset_NS_LOD_20_footprint_2 [GEOJSON] (reader GEOJSON_1)
    attributes: GeoNS_LOD0_planläge string, GeoNS_LOD0_höjdläge string, Geometriredovisning_Ytgeometri_Koordinatsystem_i_plan string, Geometriredovisning_Ytgeometri_Höjdsystem string, Geometriredovisning_lägesbestämningsmeetod_i_plan_konvertering_variant string, Geometriredovisning_lägesbestämningsmeetod_i_höjd_konvertering_variant string, Geometriredovisning_följer_mätanvisningar string, Variant_NS_LOD string
    -> Extruder_7
UndervisningsHuset_NS_LOD_20_footprint [GEOJSON] (reader GEOJSON_1)
    attributes: GeoNS_LOD0_planläge string, GeoNS_LOD0_höjdläge string, Geometriredovisning_Ytgeometri_Koordinatsystem_i_plan string, Geometriredovisning_Ytgeometri_Höjdsystem string, Geometriredovisning_lägesbestämningsmeetod_i_plan_konvertering_variant string, Geometriredovisning_lägesbestämningsmeetod_i_höjd_konvertering_variant string, Geometriredovisning_följer_mätanvisningar string, Variant_NS_LOD string
    -> Extruder_7
Extruder_7
    DIRECTION = Auto
    DISTANCE = 50
    EXTRUDED -> Clipper_2 [CLIPPER]
UndervisningsHuset_NS_LOD_20_roof [GEOJSON]00 (reader GEOJSON_1)
    attributes: GeoNS_LOD0_planläge string, GeoNS_LOD0_höjdläge string, Geometriredovisning_Ytgeometri_Koordinatsystem_i_plan string, Geometriredovisning_Ytgeometri_Höjdsystem string, Geometriredovisning_lägesbestämningsmeetod_i_plan_konvertering_variant string, Geometriredovisning_lägesbestämningsmeetod_i_höjd_konvertering_variant string, Geometriredovisning_följer_mätanvisningar string, Variant_NS_LOD string
    -> Dissolver
Dissolver
    ACCUM_INPUT_ATTRS = Use Attributes From One Feature
    CLEANING_TOLERANCE = Automatic
    CONNECT_Z_MODE = First Wins
    DEAGGREGATE_INPUT = Yes
    AREA -> Extruder_9
Extruder_9
    DIRECTION = Auto
    DISTANCE = -50
    EXTRUDED -> Clipper_2 [CLIPPEE]
Clipper_2
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> GeometryValidator_2
GeometryValidator_2
    ISSUE_ATTR_NAME = _issues
    PRESETS = Custom
    REPAIR = Yes
    RULES = PLANAR_SURFACE CHECK_AREA]DO_NOT_CHECK_AREA]TOLERANCE_MODE]AUTO]TOLERANCE]0.0]ANGULAR_TOLERANCE_MODE]Automatic]ANGULAR_TOLERANCE]0.0]FME_CONTROLLER_QUERY_FILE]transformers/dependencies/geometryvalidator/PLANAR_SURFACE.fme
    SUMMARY = Detailed
    PASSED -> GeometryValidator
    REPAIRED -> GeometryValidator
GeometryValidator
    ISSUE_ATTR_NAME = _issues
    PRESETS = Custom
    REPAIR = Yes
    RULES = "MISSING_VERTEX_NORMALS "
    SUMMARY = Detailed
    PASSED -> GeometryPropertySetter
    REPAIRED -> GeometryPropertySetter
GeometryPropertySetter
    CNT_ATTR = _count
    DOMAIN = counter
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor_2
    SET -> AttributeCreator_4
GeometryPartExtractor_2
    GQUERY:
      for $geom in //geometry
      where $geom/@fme_geometry_type = 'IFMEFace'
      return number($geom/@fme_id)
    EXTRACTED -> MeasureExtractor
MeasureExtractor
    GEOM_TYPE = Individual Vertex by Index
    INDEX = 0
    MEASURE_ATTR = _normal_z
    MEASURE_NAME = fme_vertex_normal_z
    -> TestFilter_2
TestFilter_2
    DEFAULT_VALUE = WallSurface
    TEST_LIST = "BOOL_OP,OR,COMPOSITE_TEST,""""""1"""""",TEST_CLAUSE,TEST @Value(_normal_z) = -1",GroundSurface,"BOOL_OP,OR,COMPOSITE_TEST,""""""1"""""",TEST_CLAUSE,TEST @Value(_normal_z) > 0.5",RoofSurface
    GroundSurface -> AttributeCreator_6
    RoofSurface -> SurfaceDissolver
    WallSurface -> SurfaceDissolver_2
AttributeCreator_6
    ATTR_TABLE:
      SET_TO feature_type = GroundSurface
      SET_TO parent_name = dummy_UUID_02
      SET_TO _uuid = gml_@UUID()
    -> Junction_2
    -> Junction_3
SurfaceDissolver
    ACCUM_INPUT_ATTRS = Use Attributes From One Feature
    DEAGGREGATE_INPUT = Yes
    MATCHING_APPS = No
    NORMAL_TOLERANCE = 10
    OFFSET_TOLERANCE = 1
    SEPARATE_SURFACES = No
    SURFACE -> AttributeCreator_7
AttributeCreator_7
    ATTR_TABLE:
      SET_TO feature_type = RoofSurface
      SET_TO parent_name = dummy_UUID_02
      SET_TO _uuid = gml_@UUID()
    -> Junction_2
    -> Junction_3
SurfaceDissolver_2
    ACCUM_INPUT_ATTRS = Use Attributes From One Feature
    DEAGGREGATE_INPUT = Yes
    MATCHING_APPS = No
    NORMAL_TOLERANCE = 0.0001
    OFFSET_TOLERANCE = 2
    SEPARATE_SURFACES = No
    SURFACE -> AttributeCreator_8
AttributeCreator_8
    ATTR_TABLE:
      SET_TO feature_type = WallSurface
      SET_TO parent_name = dummy_UUID_02
      SET_TO _uuid = gml_@UUID()
    -> Junction_2
    -> Junction_3
Junction_2
    -> FeatureMerger_2 [REQUESTOR]
Junction_3
    -> AttributeCreator_12
AttributeCreator_12
    ATTR_TABLE = SET_TO polygon_id = @Value(_uuid)_polygon
    -> GeometryPropertySetter_4
GeometryPropertySetter_4
    GQUERY:
      for $geom in //geometry
      where $geom/@fme_geometry_type = 'IFMEFace'
      return number($geom/@fme_id)
    OVERWRITE_CHOICE = Yes
    REMOVE_ATTRIBUTE = No
    SETTYPE_PARAM = Traits From Attributes
    SRC_ATTRS = polygon_id
    SET -> GeometryPropertyRenamer_2
GeometryPropertyRenamer_2
    GQUERY:
      for $geom in //geometry
      where $geom/@fme_geometry_type = 'IFMEFace'
      return number($geom/@fme_id)
    PARAM_LIST = polygon_id,gml_id
    RENAMETYPE_PARAM = Traits
    RENAMED -> AttributeCreator_9
AttributeCreator_9
    ATTR_TABLE = SET_TO xlink_href = #@Value(polygon_id)
    -> GeometryPropertySetter_5
GeometryPropertySetter_5
    OVERWRITE_CHOICE = Yes
    REMOVE_ATTRIBUTE = No
    SETTYPE_PARAM = Traits From Attributes
    SRC_ATTRS = xlink_href
    SET -> FeatureMerger_3 [REQUESTOR]
AttributeCreator_4
    ATTR_TABLE:
      SET_TO citygml_level_of_detail = 2
      SET_TO gml_id = gml_@UUID()
      SET_TO gml_name = dummy_UUID_02
    -> FeatureMerger_2 [SUPPLIER]
FeatureMerger_2
    ATTR_ACCUM_MODE = Prefix Supplier
    IGNORE_NULLS = No
    JOIN_KEYS = @Value(parent_name) @Value(gml_name) AUTO
    MERGE_TYPE = Attributes Only
    PROCESS_DUPS = NO
    REJECT_NULL_MISSING_KEYS = No
    SUPPLIERS_FIRST = No
    SUPPLIER_PREFIX = suppl_
    MERGED -> AttributeKeeper_3
AttributeKeeper_3
    CREATE_BULK_MODE_FEATURES = NO
    KEEP_ATTRS = _uuid,feature_type,suppl_gml_id
    -> AttributeCreator_13
AttributeCreator_13
    ATTR_TABLE:
      SET_TO citygml_level_of_detail = 2
      SET_TO gml_id = @Value(_uuid)
      SET_TO gml_parent_id = @Value(suppl_gml_id)
    -> Aggregator_3
    -> FeatureMerger_3 [SUPPLIER]
Aggregator_3
    ACCUM_ATTRS_NAME = Use Attributes From One Feature
    AGGREGATE_TYPE = Homogeneous Collection (If Possible)
    GROUP_BY = gml_id
    MODE = Geometry - Assemble One Level
    SEP = ,
    AGGREGATE -> GeometryPropertySetter_2
GeometryPropertySetter_2
    GQUERY:
      for $geom in //geometry
      where $geom/@fme_geometry_type = 'IFMEMultiSurface'
      return number($geom/@fme_id)
    OVERWRITE_CHOICE = Yes
    REMOVE_ATTRIBUTE = No
    SETTYPE_PARAM = Traits From Attributes
    SRC_ATTRS = gml_id
    SET -> AttributeCreator_10
AttributeCreator_10
    ATTR_TABLE = SET_TO polygon_id = @Value(gml_id)_polygon
    -> GeometryPropertySetter_3
GeometryPropertySetter_3
    GQUERY:
      for $geom in //geometry
      where $geom/@fme_geometry_type = 'IFMEFace'
      return number($geom/@fme_id)
    OVERWRITE_CHOICE = Yes
    REMOVE_ATTRIBUTE = No
    SETTYPE_PARAM = Traits From Attributes
    SRC_ATTRS = polygon_id
    SET -> GeometryPropertyRenamer
GeometryPropertyRenamer
    GQUERY:
      for $geom in //geometry
      where $geom/@fme_geometry_type = 'IFMEFace'
      return number($geom/@fme_id)
    PARAM_LIST = polygon_id,gml_id
    RENAMETYPE_PARAM = Traits
    RENAMED -> CityGMLGeometrySetter_3
CityGMLGeometrySetter_3
    GEOM = lod2MultiSurface
    ROLE = boundedBy
    -> GeometryPropertyRemover_3
GeometryPropertyRemover_3
    GQUERY:
      for $geom in //geometry
      where $geom/@fme_geometry_type = 'IFMEPolygon'
      return number($geom/@fme_id)
    REMOVETYPE_PARAM = Traits
    REMOVE_ALL = Yes
    REMOVED -> GeometryPropertyRemover_4
GeometryPropertyRemover_4
    GQUERY:
      for $geom in //geometry
      where $geom/@fme_geometry_type = 'IFMEMultiSurface'
      return number($geom/@fme_id)
    REGEX_FILTER = gml_id
    REMOVETYPE_PARAM = Traits
    REMOVE_ALL = No
    REMOVED -> TestFilter_4
TestFilter_4
    DEFAULT_VALUE = <UNFILTERED>
    TEST_LIST = "BOOL_OP,OR,COMPOSITE_TEST,""""""1"""""",TEST_CLAUSE,TEST @Value(feature_type) = RoofSurface",RoofSurface,"BOOL_OP,OR,COMPOSITE_TEST,""""""1"""""",TEST_CLAUSE,TEST @Value(feature_type) = WallSurface",WallSurface,"BOOL_OP,OR,COMPOSITE_TEST,""""""1"""""",TEST_CLAUSE,TEST @Value(feature_type) = GroundSurface",GroundSurface
    RoofSurface -> RoofSurface (writer CITYGML_1)
    WallSurface -> WallSurface (writer CITYGML_1)
    GroundSurface -> GroundSurface (writer CITYGML_1)
RoofSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
WallSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
GroundSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
FeatureMerger_3
    ATTR_ACCUM_MODE = Prefix Supplier
    IGNORE_NULLS = No
    JOIN_KEYS = @Value(_uuid) @Value(gml_id) AUTO
    MERGE_TYPE = Attributes Only
    PROCESS_DUPS = NO
    REJECT_NULL_MISSING_KEYS = No
    SUPPLIERS_FIRST = No
    SUPPLIER_PREFIX = suppl_
    MERGED -> Aggregator_2
Aggregator_2
    ACCUM_ATTRS_NAME = Use Attributes From One Feature
    AGGREGATE_TYPE = Homogeneous Collection (If Possible)
    GROUP_BY = parent_name
    MODE = Geometry - Assemble One Level
    SEP = ,
    AGGREGATE -> GeometryCoercer
GeometryCoercer
    GQUERY:
      for $geom in //geometry
      where $geom/count(parent::geometry) = 0
      return number($geom/@fme_id)
    KIND = fme_brep_solid
    COERCED -> AttributeCreator_11
AttributeCreator_11
    ATTR_TABLE:
      SET_TO citygml_lod_name = lod2Solid
      SET_TO gml_geometry = Solid
      SET_TO citygml_level_of_detail = 2
      SET_TO gml_id = @Value(suppl_gml_parent_id)
    -> CityGMLGeometrySetter_4
CityGMLGeometrySetter_4
    GEOM = lod2Solid
    ROLE = cityObjectMember
    -> GeometryPropertyRemover
GeometryPropertyRemover
    GQUERY:
      for $geom in //geometry
      where $geom/@fme_geometry_type = 'IFMEPolygon'
      return number($geom/@fme_id)
    REMOVETYPE_PARAM = Traits
    REMOVE_ALL = Yes
    REMOVED -> GeometryPropertyRemover_2
GeometryPropertyRemover_2
    GQUERY:
      for $geom in //geometry
      where $geom/@fme_geometry_type = 'IFMEFace'
      return number($geom/@fme_id)
    REGEX_FILTER = gml_geometry
    REMOVETYPE_PARAM = Traits
    REMOVE_ALL = No
    REMOVED -> AttributeKeeper_2
AttributeKeeper_2
    CREATE_BULK_MODE_FEATURES = NO
    KEEP_ATTRS = citygml_level_of_detail,gml_geometry,gml_id,citygml_lod_name
    -> Building (writer CITYGML_1)
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
