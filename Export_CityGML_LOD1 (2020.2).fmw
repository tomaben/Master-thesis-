FME workspace Export_CityGML_LOD1 (2020.2).fmw

Parameters:
- gml_id_export = gml_2fd46406-1213-4f63-8fcc-b4a0d69b9911   # gml_id export
- DestDataset_CITYGML = $(FME_MF_DIR)Output_script\Multihuset_LOD_1.3.gml   # Destination CityGML Document

Writers:
- CITYGML_1: CITYGML to $(DestDataset_CITYGML)

Starter
    -> SQLExecutor [INITIATOR]
SQLExecutor
    COMBINE_ATTRS = Result Attributes Only
    COMBINE_GEOM = Initiator Geometry Only
    DATASET = postgres
    EXPOSED_ATTRIBUTE_LIST = cityobjectid
    FORMAT = POSTGIS
    POSTGIS_CREATE_FEATURE_TABLES_FROM_DATA = Yes
    POSTGIS_DISABLE_COLLECTION_SPLITTING = yes
    POSTGIS_NAMED_CONNECTION = postgres
    POSTGIS_QUERY_FEATURE_TYPES_FOR_MERGE_FILTERS = Yes
    POSTGIS_READ_TIME_WITH_TIMEZONE = Yes
    POSTGIS_USE_TRUE_POSTGIS_TYPES = yes
    SQL_STATEMENT:
      SELECT id as cityobjectid
      FROM citydb.cityobject
      WHERE gmlid = '$(gml_id_export)'
    RESULT -> SQLExecutor_2 [INITIATOR]
SQLExecutor_2
    COMBINE_ATTRS = Result Attributes Only
    COMBINE_GEOM = Initiator Geometry Only
    DATASET = postgres
    EXPOSED_ATTRIBUTE_LIST = solid
    FORMAT = POSTGRES
    POSTGRES_CREATE_FEATURE_TABLES_FROM_DATA = Yes
    POSTGRES_NAMED_CONNECTION = postgres
    POSTGRES_QUERY_FEATURE_TYPES_FOR_MERGE_FILTERS = Yes
    POSTGRES_READ_TIME_WITH_TIMEZONE = Yes
    SQL_STATEMENT:
      SELECT solid_geometry as solid
      FROM citydb.surface_geometry
      WHERE cityobject_id = '@Value(cityobjectid)'
    RESULT -> GeometryReplacer
GeometryReplacer
    ELLIPSOID_NAME = WGS84
    KIND_LONG = Hex Encoded OGC Well Known Binary
    LETTERING = WGS84
    MSSQL_FORMAT_CHOICE = Geometry
    OGC_WKT_PRECISION_DISPLAY = 64-bit
    OUTPUT_POINT_DISPLAY = Point
    REMOVE_ATTRIBUTE = Yes
    SOURCE = @Value(solid)
    SRS_AXIS_ORDER_DISPLAY = Automatic
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> FaceReplacer
FaceReplacer
    ANGULAR_TOLERANCE_CHOICE = Automatic
    THICKNESS_TOLERANCE_CHOICE = Automatic
    -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> GeometryCoercer
GeometryCoercer
    GQUERY:
      for $geom in //geometry
      where $geom/count(parent::geometry) = 0
      return number($geom/@fme_id)
    KIND = fme_brep_solid
    COERCED -> AttributeCreator
AttributeCreator
    ATTR_TABLE:
      SET_TO gml_id = $(gml_id_export)
      SET_TO citygml_level_of_detail = 1
    -> AttributeKeeper
AttributeKeeper
    CREATE_BULK_MODE_FEATURES = NO
    KEEP_ATTRS = citygml_level_of_detail,gml_id
    -> CityGMLGeometrySetter
CityGMLGeometrySetter
    GEOM = lod1Solid
    ROLE = cityObjectMember
    -> Building (writer CITYGML_1)
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer

FME custom transformer Starter
This transformer is intended to start a workspace branch without the use of the creator transformer. This will end up without additional attributes (_creation_instance) at the end of the workspace.

Creator
    GEOMTYPE = Geometry Object
    NUM = 1
    CREATED -> Output (output)
Output (output)
